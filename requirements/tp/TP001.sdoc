[DOCUMENT]
TITLE: Test Plan - Iron-Air Modeling
UID: DOC-TP001
VERSION: 0.1.0

[REQUIREMENT]
UID: TP001
TITLE: Test levels
STATEMENT: >>>
Testing SHALL include (1) atomic MATLAB unit tests per physics block, (2) cell integration / mock V-I regression, (3) stack/pack aggregation checks, (4) plant 24-100 h arbitrage with ride-through monitors.
<<<

[REQUIREMENT]
UID: TP002
TITLE: Tooling
STATEMENT: >>>
Unit tests SHALL use the MATLAB Unit Testing Framework under tests/ and be invoked via `make test`.
<<<

[REQUIREMENT]
UID: TP003
TITLE: Mock-data acceptance
STATEMENT: >>>
Cell voltage RMSE against mock discharge curves SHALL be within 50 mV for the reference constant-current case after parameter lock.
<<<

[REQUIREMENT]
UID: TP004
TITLE: Requirements validation
STATEMENT: >>>
`make strictdoc-validate` SHALL pass before release commits that change requirements.
<<<
