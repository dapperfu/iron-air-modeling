[DOCUMENT]
TITLE: Software Design Document - Iron-Air First-Principles Model
UID: DOC-SDD001
VERSION: 0.1.0

[REQUIREMENT]
UID: SDD001
TITLE: Discretization
STATEMENT: >>>
Each 1D domain uses Nx control volumes. State vectors are length Nx (or species×Nx). Spatial operators use second-order central differences with Neumann/Dirichlet boundaries as documented in src/ ironair_*_ode.m files.
<<<

[REQUIREMENT]
UID: SDD002
TITLE: Cell voltage equation
STATEMENT: >>>
Cell voltage is V = E_eq(c,T) - eta_metal - eta_air - I*R_elec where eta_air selects ORR (discharge, I>0 convention discharge positive) or OER (charge).
<<<

[REQUIREMENT]
UID: SDD003
TITLE: HER kinetics
STATEMENT: >>>
H2 evolution uses Tafel/Butler-Volmer form i_H2 = i0_H2 * exp(alpha_H2*F*eta_H2/(R*T)) gated by metal overpotential; n_dot_H2 = i_H2*A/(2*F); Faradaic efficiency eta_F = 1 - I_H2/(abs(I)+eps).
<<<

[REQUIREMENT]
UID: SDD004
TITLE: Solver guidance
STATEMENT: >>>
Recommended solvers: ode15s or ode23tb; RelTol 1e-4; AbsTol 1e-6 (concentration) / 1e-3 (temperature). Documented in model ConfigSet of demos.
<<<

[REQUIREMENT]
UID: SDD005
TITLE: Multi-rate strategy
STATEMENT: >>>
Fast electrical signals (V, I, ride-through) use continuous or small fixed step; thermal uses continuous with larger thermal mass; plant schedule uses slow exogenous From Workspace profiles. Rate Transition blocks separate domains in plant demo.
<<<

[REQUIREMENT]
UID: SDD006
TITLE: Mask and requirement citation
STATEMENT: >>>
Each masked library block documentation pane SHALL cite relevant SSS/SRS UIDs.
<<<
