[DOCUMENT]
TITLE: Interface Requirements Specification - IRONAIR Public APIs
UID: DOC-IRS001
VERSION: 1.1.0
OPTIONS:
  MARKUP: Text

[[SECTION]]
UID: SEC-IRS-PY
TITLE: Python package interfaces

[TEXT]
STATEMENT: >>>
This Interface Requirements Specification (IRS) covers Python public APIs and the
physical interfaces of the patented plant that those APIs must expose as named
inputs, outputs, and couplings: air, electrolyte, electrical tabs, stacking
contacts, and charge/discharge electrode selection (US12308414B2 and EP4602674A1).
<<<

[REQUIREMENT]
UID: IA-IRS-001
STATUS: Active
TITLE: Public package imports
STATEMENT: >>>
The following imports SHALL succeed after editable install:

  import ironair
  from ironair import constants
  from ironair import chemistry
  from ironair import components
  from ironair import simulation
  from ironair import scenarios

ironair SHALL NOT export a plotting, seaborn, matplotlib, or pandas API.
<<<
COMMENT: >>>
Changed because ironair.plotting was removed. The physics imports succeed after
editable install. Plotting is notebook code under plant_sim, not an ironair import.
<<<
RELATIONS:
- TYPE: Parent
  VALUE: IA-SYS-001

[REQUIREMENT]
UID: IA-IRS-002
STATUS: Active
TITLE: RHS signature
STATEMENT: >>>
Every dynamic component SHALL expose:

  def rhs(self, t, y, inputs, context) -> numpy.ndarray

t is time in seconds, y is a 1-D float64 state vector, inputs is a mapping of named
physical inputs, and context carries shared couplings without hidden mutation of
component parameters.
<<<
COMMENT: >>>
Signature inspection and a deterministic double-evaluation test pass for each component.
<<<
RELATIONS:
- TYPE: Parent
  VALUE: IA-ODE-001

[REQUIREMENT]
UID: IA-IRS-003
STATUS: Active
TITLE: CoupledSystem simulate interface
STATEMENT: >>>
ironair.simulation.CoupledSystem.simulate SHALL accept t_span, optional t_eval,
optional inputs callable, solver method, and tolerances, and SHALL return a
SimulationResult.

t_span SHALL accept LODES windows including 8 h, 100 h (3.6e5 s), 300 h, and
multi-day values from US12308414B2 without changing parameter objects.
<<<
COMMENT: >>>
Default method is BDF or Radau. Result includes t, y, state_names, and diagnostics.
<<<
RELATIONS:
- TYPE: Parent
  VALUE: IA-ODE-003

[REQUIREMENT]
UID: IA-IRS-004
STATUS: Active
TITLE: Numeric trajectory result
STATEMENT: >>>
SimulationResult SHALL carry numeric trajectories: time array t, state array y,
state names, state units, and solver diagnostics.

ironair SHALL NOT convert those trajectories to pandas or draw them.

Notebooks SHALL build a pandas DataFrame from t and y and SHALL plot that frame
with seaborn in the notebook cell. The figure SHALL be notebook output.
<<<
COMMENT: >>>
Changed because ironair.plotting and SimulationResult.to_dataframe were removed.
The physics result is arrays. DataFrame construction and sns.lineplot live in
plant_sim notebooks.
<<<
RELATIONS:
- TYPE: Parent
  VALUE: IA-NBK-003

[REQUIREMENT]
UID: IA-IRS-005
STATUS: Active
TITLE: Estimator measurement-only interface
STATEMENT: >>>
When a state estimator is implemented, it SHALL accept measurements and prior
estimates only. It SHALL NOT receive the plant hidden state vector during observer
execution. No BatteryStateEstimator class exists today (IA-EST-001 design-only).
<<<
COMMENT: >>>
Changed because BatteryStateEstimator and tests that pass MeasurementVector do not
exist. The measurement-only interface remains the allocation when an observer is added.
<<<
RELATIONS:
- TYPE: Parent
  VALUE: IA-EST-001

[[/SECTION]]

[[SECTION]]
UID: SEC-IRS-PHYS
TITLE: Patented physical interfaces

[REQUIREMENT]
UID: IA-IRS-006
STATUS: Active
TITLE: Air interface
STATEMENT: >>>
AirSystem and OxygenReduction SHALL exchange named flows for dry air or oxygen,
humidity, CO2 mole fraction, pO2, volumetric or mass flow, and manifold pressure.

ORR SHALL expose an electrolyte-facing first surface and an air-facing second
surface (EP4602674A1 Claim 1). Stacked submerged ORR sections SHALL expose per-
section pressure drop so that Claim 1 equal-dP can be enforced.

Airflow regulation structures including holed ramp arrays (US12308414B2 Claims 14-15)
SHALL appear as named hydraulic parameters, not as undocumented magic numbers.
<<<
RELATIONS:
- TYPE: Parent
  VALUE: IA-SYS-014

[REQUIREMENT]
UID: IA-IRS-007
STATUS: Active
TITLE: Electrolyte and hydraulic interface
STATEMENT: >>>
Electrolyte, Reservoir, Pump, Valve, and Pipe SHALL exchange water, KOH/NaOH/LiOH,
carbonate, dissolved oxygen, liquid volume, temperature, and leak flows.

Primary-to-secondary containment leak into vessel cavity 161 (US12308414B2
FIGS. 1E-1F) SHALL be a named leak path. Shared electrolyte baths of multiple
cells SHALL use a common electrolyte context key.
<<<
RELATIONS:
- TYPE: Parent
  VALUE: IA-SYS-021

[REQUIREMENT]
UID: IA-IRS-008
STATUS: Active
TITLE: Electrical tab and stacking interface
STATEMENT: >>>
Iron, ORR, and OER components SHALL expose named electrical ports for anode tabs,
OER cathode tabs, ORR tabs, can-negative housing, and stacking contact points
(US12308414B2 Claims 3 and 5; EP4602674A1 FIG. 8 tabs 230, 240a, 240b).

Charge and discharge paths SHALL be distinct named connections selectable by
PlantModel modes (IA-CTL-001). Bus bars outside the active-area plane (EP4602674A1
Claims 30-31) SHALL be identifiable in the state-index map.
<<<
COMMENT: >>>
Changed because SupervisoryController does not exist. PlantModel.algebraic selects
iron-OER versus iron-ORR paths.
<<<
RELATIONS:
- TYPE: Parent
  VALUE: IA-SYS-025

[REQUIREMENT]
UID: IA-IRS-009
STATUS: Active
TITLE: Channel and interdigitation interface
STATEMENT: >>>
IronAnode SHALL publish channel occupancy, ChanFrac, rib width, and whether
each channel contains OER, additive, both, or neither (EP4602674A1 Claims 5-6).

OxygenEvolution SHALL publish projection length, trunk presence, corrugated versus
discrete-cathode layout, and iron-OER gap. Separator SHALL publish ionic
resistance and bubble-egress availability between those ports.
<<<
COMMENT: >>>
Changed because IronElectrode does not exist. IronAnode and PlantParams publish
ChanFrac, rib width, and channel occupancy used by channeled-electrode notebooks.
<<<
RELATIONS:
- TYPE: Parent
  VALUE: IA-SYS-016

[REQUIREMENT]
UID: IA-IRS-010
STATUS: Active
TITLE: Scenario and architecture selection interface
STATEMENT: >>>
plant_sim.params.PlantParams plus OxygenReduction/OxygenEvolution layout flags SHALL
accept architecture identifiers covering US12308414B2 Claim 1 stacked ORR, Claim 18
DRI bed, floating ORR, and EP4602674A1 Claims 1, 20, 38, 55, 70, and 77 layouts.

Invalid combinations (for example bifunctional ORR forced to OER potential while
isolation is required) SHALL raise a documented configuration error.

ironair.scenarios SHALL NOT be treated as the architecture selector; that package
is empty. plant_sim.scenarios.mission supplies time-varying inputs, not layout IDs.
<<<
COMMENT: >>>
Changed because ironair.scenarios is an empty package. Architecture is selected by
PlantParams and ORR/OER mode flags used by DualElectrodeCell and PlantModel.
<<<
RELATIONS:
- TYPE: Parent
  VALUE: IA-SYS-006

[[/SECTION]]
