[DOCUMENT]
TITLE: Software Requirements Specification - Foundation, Chemistry, ODE, Notebooks, Verification
UID: DOC-SSS001
VERSION: 1.1.0
OPTIONS:
  MARKUP: Text

[[SECTION]]
UID: SEC-SSS1-REQ
TITLE: Requirements management

[TEXT]
STATEMENT: >>>
This document specifies foundation, chemistry, ODE, notebook, and verification
requirements for ironair. Chemical stoichiometry, capacities, electrolyte
compositions, and kinetics domains are taken from US12308414B2 and EP4602674A1.
Software tests verify implementation against these statements; they do not
validate the patents experimentally.
<<<

[REQUIREMENT]
UID: IA-REQ-001
STATUS: Active
TITLE: StrictDoc source of truth
STATEMENT: >>>
All requirements SHALL be maintained in StrictDoc .sdoc files.

Markdown SHALL be used for supplementary explanatory design documents but SHALL NOT
replace the authoritative requirements database.
<<<
COMMENT: >>>
Every IA-* UID exists in reqs/**/*.sdoc. CI fails if a source @relation UID is missing
from the StrictDoc database.
<<<
RELATIONS:
- TYPE: Parent
  VALUE: IA-SYS-001

[REQUIREMENT]
UID: IA-REQ-002
STATUS: Active
TITLE: Requirement identifiers
STATEMENT: >>>
Each requirement SHALL possess a permanent unique ID.

Required prefixes: IA-SYS, IA-REQ, IA-CON, IA-CHM, IA-FE, IA-HER, IA-ORR, IA-OER,
IA-GDL, IA-ELY, IA-SEP, IA-COL, IA-CEL, IA-THM, IA-AIR, IA-FLD, IA-HEX, IA-STK,
IA-MOD, IA-ENC, IA-DC, IA-CNV, IA-INV, IA-TRF, IA-GRD, IA-CTL, IA-EST, IA-DEG,
IA-FLT, IA-ODE, IA-NBK, IA-PLT, IA-TST, IA-DOC, IA-SDD, IA-IRS, IA-SCN, IA-TP,
IA-TD.

Patent-mapped system requirements live under IA-SYS in DOC-SRS001 (US12308414B2
Claims 1-18 and EP4602674A1 Claims 1-89). Component prefixes SHALL be used for
the corresponding physical models of those claims.
<<<
COMMENT: >>>
UID uniqueness is verified by tests. All required prefixes appear in the requirements tree.

Changed because the prefix list omitted IA-SDD, IA-IRS, IA-SCN, IA-TP, and IA-TD
even though those UIDs already exist in DOC-SDD001, DOC-IRS001, DOC-SSS003,
DOC-TP001, and DOC-TD001.
<<<

[REQUIREMENT]
UID: IA-REQ-003
STATUS: Active
TITLE: Function-level traceability
STATEMENT: >>>
Every public physics, control, solver, and scenario function SHALL contain a
StrictDoc @relation marker.

Notebook plotting SHALL be plant_sim notebook source. It SHALL NOT be an ironair
function and SHALL NOT require an @relation marker inside src/ironair.

A function implementing several requirements SHALL contain separate relation markers
for every applicable requirement.

Internal helper functions SHALL be traceable to the applicable implementation requirements.

The traceability system SHALL identify Requirement -> Python Function -> Test -> Notebook Scenario
for implemented physics in src/ironair and plant_sim.
<<<
COMMENT: >>>
Changed because CI that greps only src/ironair misses plant_sim component ODEs,
which now implement SSS002. Traceability SHALL scan src/ironair and plant_sim
for @relation markers.
<<<

[REQUIREMENT]
UID: IA-REQ-004
STATUS: Active
TITLE: Bidirectional traceability
STATEMENT: >>>
CI SHALL verify that every implementation requirement (not a design-only allocation)
has an associated function in src/ironair or plant_sim, every such function exists,
all source-level requirement references resolve to valid StrictDoc UIDs, and every
requirements-to-source reference identifies an existing Python source element.

CI SHALL verify plant_sim notebooks 01-40 and 90-99 exist. Design-only IA-SCN-*
and unimplemented observer/sensor UIDs SHALL NOT be treated as missing-notebook
failures.
<<<
COMMENT: >>>
Changed because tests/test_requirements_traceability.py does not exist and the
previous SHALL that every documented scenario has a notebook contradicted
design-only SSS003 IDs and empty ironair.scenarios. Traceability now matches
implemented plant_sim plus ironair chemistry/ODE code.
<<<

[REQUIREMENT]
UID: IA-REQ-005
STATUS: Active
TITLE: Requirement verification
STATEMENT: >>>
Every physical requirement SHALL specify acceptance criteria that can be objectively tested.

Compliance SHALL be verified through unit tests, integration tests, conservation checks,
numerical convergence tests, and documented model validation.

Passing software tests SHALL NOT be represented as physical validation against experimental hardware.
<<<
COMMENT: >>>
Physical requirements include ACCEPTANCE_CRITERIA. Validation status is tracked separately
from software verification in ironair.validation. Patent claims are traced by UID
and source citation, not by copying claim text as a test oracle.
<<<

[[/SECTION]]

[[SECTION]]
UID: SEC-SSS1-CON
TITLE: Constants, parameters, and property models

[TEXT]
STATEMENT: >>>
US12308414B2 defines room temperature as 25 C and standard temperature and
pressure as 25 C and 1 atm, with "about" meaning plus or minus 10 percent or
instrument error, whichever is larger. EP4602674A1 simulations use 6 M KOH at
303 K. Property models SHALL cover those reference states.
<<<

[REQUIREMENT]
UID: IA-CON-001
STATUS: Active
TITLE: Constants module
STATEMENT: >>>
Implement src/ironair/constants.py providing F_C_MOL, R_J_MOL_K, T_REF_K, P_REF_PA,
M_FE_KG_MOL, M_O2_KG_MOL, M_H2O_KG_MOL, and M_KOH_KG_MOL.

T_REF_K SHALL default to 298.15 K (25 C) and P_REF_PA to 101325 Pa (1 atm) to
match US12308414B2 standard ambient temperature and pressure. A 303 K property
set SHALL be available for EP4602674A1 simulation conditions.

Fundamental constants SHALL be immutable.
<<<
COMMENT: >>>
from ironair import constants succeeds. Named constants match CODATA/IUPAC values
within documented precision. Assignment to module constants raises an error or is
rejected by typing/runtime freeze.
<<<

[REQUIREMENT]
UID: IA-CON-002
STATUS: Active
TITLE: Parameter definitions
STATEMENT: >>>
Every component SHALL use explicit, typed parameter objects.

Parameters SHALL include name, value, SI unit, physical meaning, valid range,
source classification, literature reference when available, uncertainty when available,
and calibration status.

Parameter categories SHALL distinguish fundamental constant, literature value,
experimental measurement, engineering design assumption, calibrated coefficient,
and unverified placeholder.

Patent-disclosed values (electrolyte molarity, channel lengths, iron loading,
pO2 windows, theoretical mAh/g) SHALL be tagged as literature value with the
patent number and claim or paragraph in the literature-reference field. They
SHALL NOT be tagged as experimental measurement unless an independent hardware
campaign is recorded.
<<<
COMMENT: >>>
PhysicalParameter dataclass enforces required fields and rejects out-of-range values.
Unverified placeholders are queryable via calibration_status.
<<<

[REQUIREMENT]
UID: IA-CON-003
STATUS: Active
TITLE: Property models
STATEMENT: >>>
Implement concentration- and temperature-dependent properties for KOH conductivity,
KOH density, KOH viscosity, KOH heat capacity, KOH water activity, dissolved oxygen
solubility, oxygen diffusivity, gas-phase diffusivity, iron conductivity, thermal
conductivity, reaction rate constants, and electrochemical exchange-current densities.

Property models SHALL enforce their valid domains.

KOH molarity domain SHALL include the patented compositions 5 M to 11 M hydroxide,
including 6 M KOH, 5.5 M KOH + 0.5 M LiOH, 6 M NaOH, 5 M NaOH + 1 M KOH, and
7 M or greater hydroxide (US12308414B2 electrolyte examples; EP4602674A1
[0231]-[0241]).
<<<
COMMENT: >>>
Property functions raise a domain error outside documented T and concentration ranges
and return finite SI values inside the range.
<<<
RELATIONS:
- TYPE: Parent
  VALUE: IA-SYS-021

[[/SECTION]]

[[SECTION]]
UID: SEC-SSS1-CHM
TITLE: Shared iron-air chemistry (US12308414B2 and EP4602674A1)

[TEXT]
STATEMENT: >>>
EP4602674A1 Equations 1-2 and US12308414B2 air-electrode half-reactions are the
stoichiometric source for ironair.chemistry. Elemental conservation is a software
requirement; the patents supply the reaction identities and theoretical capacities.
<<<

[REQUIREMENT]
UID: IA-CHM-001
STATUS: Active
TITLE: Stoichiometric reaction network
STATEMENT: >>>
Implement a common chemical reaction network.

Mathematical model:

  dn/dt = S @ r + B @ q

Where S is the chemical stoichiometric matrix, r is the reaction-rate vector,
B maps boundary flows to species inventories, and q is the boundary-flow vector.

The reaction network SHALL enforce elemental conservation.
<<<
COMMENT: >>>
For every reaction column, elemental composition @ S[:, j] is numerically zero.
<<<
RELATIONS:
- TYPE: Parent
  VALUE: IA-SYS-002

[REQUIREMENT]
UID: IA-CHM-002
STATUS: Active
TITLE: Iron conversion
STATEMENT: >>>
Implement Fe + 2OH- <-> Fe(OH)2 + 2e- as EP4602674A1 [0042] Equation 1.

Calculate reaction rates from electrode kinetics and Faraday's law.

Theoretical first-step capacity SHALL be 960 mAh per gram of metallic Fe
(EP4602674A1 [0043]). Net volume increase on discharge SHALL be accommodated in
anode porosity rather than by creating unphysical inventory.
<<<
RATIONALE: >>>
EP4602674A1 [0042]-[0043]. US12308414B2 identifies Fe and Fe-alloys (FeAl, FeZn,
FeMg) as metal-electrode options; iron is the default LODES anode.
<<<
COMMENT: >>>
Two electrons per iron atom. Faraday mapping r = i * A / (n * F) holds within solver tolerance.
<<<
RELATIONS:
- TYPE: Parent
  VALUE: IA-SYS-020

[REQUIREMENT]
UID: IA-CHM-003
STATUS: Active
TITLE: Magnetite formation
STATEMENT: >>>
Implement configurable conversion between iron hydroxide and magnetite, including
electron transfer and correct stoichiometry.

The second discharge step SHALL correspond to further oxidation of Fe(OH)2 to
Fe3O4 with theoretical capacity 320 mAh per gram of Fe (EP4602674A1 [0043]
Equation 2). Charge SHALL reduce higher-valence iron species toward Fe(0)
(EP4602674A1 [0049]).
<<<
RATIONALE: >>>
EP4602674A1 [0042]-[0043], [0049]. Magnetite is the example higher-valence product
on discharge through the dual-electrode load path.
<<<
COMMENT: >>>
Default electrochemical path conserves Fe, O, H, and charge. A Schikorr chemical path
may be enabled without inventing extra electrons.
<<<
RELATIONS:
- TYPE: Parent
  VALUE: IA-SYS-020

[REQUIREMENT]
UID: IA-CHM-004
STATUS: Active
TITLE: Oxygen reduction reaction
STATEMENT: >>>
Implement O2 + 2H2O + 4e- -> 4OH- as the ORR discharge reaction of
US12308414B2 (four-electron oxygen reduction at the gas-solid-electrolyte
triple-phase boundary).

ORR SHALL consume gaseous oxygen typically sourced from air and SHALL require
triple-phase contact among O2, an electronically conductive solid, and
electrolyte.
<<<
RATIONALE: >>>
US12308414B2 detailed description of cathode 120 / GDE operation. EP4602674A1
FIG. 1 ORR electrode 104 is the discharge positive.
<<<
COMMENT: >>>
Four electrons per O2. OH- production matches Faraday's law.
<<<
RELATIONS:
- TYPE: Parent
  VALUE: IA-SYS-020

[REQUIREMENT]
UID: IA-CHM-005
STATUS: Active
TITLE: Oxygen evolution reaction
STATEMENT: >>>
Implement 4OH- -> O2 + 2H2O + 4e- as the OER charge reaction on a dedicated
OER electrode (US12308414B2 dual cathode; EP4602674A1 [0048]-[0049]).

OER kinetics, catalyst state, and bubble generation SHALL be independent of ORR
so that high OER potentials do not oxidize the ORR electrode when the electrodes
are electrically separated (US12308414B2 FIGS. 5A-5B).
<<<
RATIONALE: >>>
Dual-electrode configuration in both patents. EP4602674A1 Claim 11: OER as porous
metal mesh plus oxygen-evolution catalyst (Ni, Ni-Fe, Mn oxide, Fe, NiOx,
NiOx(OH)y, FeOx, FeOx(OH)y).
<<<
COMMENT: >>>
OER is the reverse four-electron oxygen couple of ORR with independent kinetics.
<<<
RELATIONS:
- TYPE: Parent
  VALUE: IA-SYS-020

[REQUIREMENT]
UID: IA-CHM-006
STATUS: Active
TITLE: Hydrogen evolution reaction
STATEMENT: >>>
Implement 2H2O + 2e- -> H2 + 2OH- as the parasitic hydrogen evolution reaction
that competes with iron recharge (EP4602674A1 [0044], [0047]).

HER SHALL be favored at the electrode front when ionic path length to unreacted
oxidized iron at the back is large. Channeled and interdigitated geometries
SHALL reduce that path length and SHALL be able to increase coulombic efficiency
relative to planar electrodes (EP4602674A1 FIGS. 19-21).
<<<
RATIONALE: >>>
EP4602674A1 [0044]-[0050] and FIGS. 19-26. Water as HER reactant can be replenished
while iron hydroxide at the back remains transport-limited.
<<<
COMMENT: >>>
Two electrons per H2. Rate increases with more negative iron overpotential.
<<<
RELATIONS:
- TYPE: Parent
  VALUE: IA-SYS-020

[REQUIREMENT]
UID: IA-CHM-007
STATUS: Active
TITLE: Butler-Volmer kinetics
STATEMENT: >>>
Implement nonlinear electrode kinetics with exchange-current density, transfer coefficients,
local overpotential, temperature, species activities, electrode surface area, and
reaction availability.

Exchange-current densities SHALL be temperature- and concentration-dependent
within the patented alkaline domain. Interdigitated OER SHALL be allowed to
lower effective ionic overpotential relative to planar OER at the same loading
(EP4602674A1 FIGS. 19-24).
<<<
COMMENT: >>>
Zero overpotential yields zero net Faradaic current at unit activities. Current is
odd in overpotential for symmetric coefficients.
<<<

[REQUIREMENT]
UID: IA-CHM-008
STATUS: Active
TITLE: Nernst potentials
STATEMENT: >>>
Calculate equilibrium potentials using thermodynamically consistent activities and
standard electrode-potential references.
<<<
COMMENT: >>>
Nernst potentials shift (RT/nF) ln(activity quotient) relative to documented E0.
<<<

[REQUIREMENT]
UID: IA-CHM-009
STATUS: Active
TITLE: Reaction thermodynamics
STATEMENT: >>>
Calculate Gibbs free energy, reaction enthalpy, reaction entropy, equilibrium cell
potential, reversible reaction heat, and irreversible reaction heat.
<<<
COMMENT: >>>
E_eq = -DeltaG / (n F). Irreversible heat is eta * i * A. Reversible heat uses T * DeltaS.
<<<

[REQUIREMENT]
UID: IA-CHM-010
STATUS: Active
TITLE: Chemistry conservation
STATEMENT: >>>
The central chemistry module SHALL check iron atom conservation, oxygen atom conservation,
hydrogen atom conservation, potassium conservation, carbon conservation, charge balance,
electron transfer, and reaction stoichiometry.
<<<
COMMENT: >>>
Elemental residual norms are below 1e-12 relative to characteristic inventory for
closed-system reaction extents.
<<<

[REQUIREMENT]
UID: IA-CHM-011
STATUS: Active
TITLE: Coulombic efficiency versus electrode architecture
STATEMENT: >>>
The chemistry-to-electrode coupling SHALL report instantaneous coulombic charge
efficiency as the fraction of charge current stored in intended iron reduction
products rather than HER (EP4602674A1 [0044], FIGS. 19, 21, 23, 25).

Planar, channeled, and interdigitated OER/iron layouts SHALL be comparable on
the same ParameterSet. Interdigitated layouts SHALL be able to show higher
coulombic efficiency and lower sensitivity of efficiency to areal loading than
planar layouts, matching the qualitative simulation results of EP4602674A1
FIGS. 19-24 at 6 M KOH, 303 K, initial rib porosity 0.6, example ChanFrac 0.4,
w_rib 5 mm, and example loading 4 g Fe/cm2.
<<<
RATIONALE: >>>
EP4602674A1 [0261]-[0280] and FIGS. 19-27. FIG. 27 experimental interdigitated
cell showed an extended upper discharge voltage plateau versus planar control
at matched loading, temperature, current, electrolyte, and ORR.
<<<
RELATIONS:
- TYPE: Parent
  VALUE: IA-SYS-015

[[/SECTION]]

[[SECTION]]
UID: SEC-SSS1-ODE
TITLE: ODE protocol, solvers, and multiscale execution

[REQUIREMENT]
UID: IA-ODE-001
STATUS: Active
TITLE: Common component protocol
STATEMENT: >>>
Every dynamic component SHALL implement rhs(self, t, y, inputs, context).

The RHS SHALL be deterministic for a fixed state, time, input, and parameter configuration.

It SHALL NOT modify component state through hidden side effects.
<<<
COMMENT: >>>
Repeated rhs evaluations with identical arguments return identical arrays. Component
parameter objects are unchanged after rhs.
<<<
RELATIONS:
- TYPE: Parent
  VALUE: IA-SYS-003

[REQUIREMENT]
UID: IA-ODE-002
STATUS: Active
TITLE: State definitions
STATEMENT: >>>
Each component SHALL publish named state metadata and a validated state vector layout.

State arrays SHALL be NumPy arrays.
<<<
COMMENT: >>>
y0 size matches len(state_specs). Units and names are unique per component.
<<<

[REQUIREMENT]
UID: IA-ODE-003
STATUS: Active
TITLE: Coupled solver
STATEMENT: >>>
Implement ironair.simulation.CoupledSystem.

The solver SHALL assemble component states into one global state vector, maintain a
state-index map, resolve shared inputs and algebraic couplings, evaluate the coupled
RHS, pass the assembled system to SciPy, detect numerical failures, and return state
trajectories and diagnostics.
<<<
COMMENT: >>>
simulate() returns a SimulationResult with t, y, names, and solver diagnostics.
Failure of solve_ivp is reported rather than silently truncated.
<<<

[REQUIREMENT]
UID: IA-ODE-004
STATUS: Active
TITLE: Stiff solvers
STATEMENT: >>>
The default integrated system SHALL use a stiff-capable solver, normally SciPy BDF or Radau.

Nonstiff component demonstrations MAY use RK45 or DOP853.
<<<
COMMENT: >>>
CoupledSystem default method is BDF or Radau.
<<<

[REQUIREMENT]
UID: IA-ODE-005
STATUS: Active
TITLE: Numerical robustness
STATEMENT: >>>
The simulation SHALL include state-specific absolute tolerances, relative tolerances,
Jacobian sparsity, event detection, hybrid mode transitions, nonnegative inventory
checks, solver diagnostics, and energy and mass conservation residuals.
<<<
COMMENT: >>>
SimulationResult exposes atol vector, events, conservation residuals, and solver status.
<<<

[REQUIREMENT]
UID: IA-ODE-006
STATUS: Active
TITLE: Multiscale execution
STATEMENT: >>>
The system SHALL support millisecond, second, minute, hour, and multi-day simulation windows.

Detailed electrochemical dynamics and long-duration grid dispatch SHALL be able to use
different model fidelity settings while sharing the same physical parameter definitions.
<<<
COMMENT: >>>
The same ParameterSet can be passed to detailed and reduced-order components.
t_span may be [0, 1e-3] or [0, 7*86400] without changing parameter objects.
LODES windows of 8 h, 100 h, 300 h, week-scale, and seasonal duration from
US12308414B2 SHALL use the same ParameterSet with documented fidelity flags.
<<<
RELATIONS:
- TYPE: Parent
  VALUE: IA-SYS-007

[[/SECTION]]

[[SECTION]]
UID: SEC-SSS1-NBK
TITLE: Notebooks and plotting

[REQUIREMENT]
UID: IA-NBK-001
STATUS: Active
TITLE: Notebook development environment
STATEMENT: >>>
Component, substructure, plant, and scenario notebooks SHALL live under plant_sim/
using the decade numbering in plant_sim/README.md (01-09 components through 90-99
scenarios).

Chemistry demonstration notebooks MAY live under notebooks/chemistry when created.

Notebooks SHALL import numerical models from plant_sim and ironair.chemistry.
No notebook SHALL contain a separate replacement implementation of a battery physics model.
<<<
COMMENT: >>>
Changed because the notebooks/ tree does not exist; plant_sim/*.ipynb are the
implemented component-to-plant notebooks. Requiring notebooks/ would make the
SHALL unverifiable against the plant_sim ODE stack.
<<<

[REQUIREMENT]
UID: IA-NBK-002
STATUS: Active
TITLE: Seaborn visualization in the notebook
STATEMENT: >>>
Scenario notebooks SHALL call seaborn directly in the notebook cell for the
principal plots. They SHALL NOT call an ironair plotting API or a project
plotting helper to draw those figures.

Matplotlib MAY create the figure, set labels, and add a short assumption note.

Plots SHALL include a title, axis labels with physical units, a legend where
more than one series is drawn, and the physical operating assumption.

The figure SHALL render as notebook cell output.
<<<
COMMENT: >>>
Changed because plots were drawn by plant_sim.plotting, which saved a PNG and
closed the figure. Notebook cells now build a pandas DataFrame and call
sns.lineplot. The matplotlib inline backend publishes the figure as display_data.
<<<

[REQUIREMENT]
UID: IA-NBK-003
STATUS: Active
TITLE: Physics package excludes plotting
STATEMENT: >>>
The ironair package SHALL contain atomic ODE and other plant equations only.

ironair SHALL NOT include plotting, matplotlib, seaborn, plotly, image I/O,
figure styling, or pandas data-visualization.

Notebooks SHALL build pandas DataFrames from the numeric trajectories ironair
or plant_sim returns, SHALL plot those frames with seaborn in the cell, and
SHALL display the figure in the notebook.
<<<
COMMENT: >>>
Changed because ironair.plotting and plot_states were removed. src/ironair has
no matplotlib, seaborn, or pandas import. plant_sim notebooks call sns.lineplot.
<<<

[REQUIREMENT]
UID: IA-NBK-004
STATUS: Active
TITLE: Chemical model demonstrations
STATEMENT: >>>
Immediately after implementing the baseline chemistry, create notebooks demonstrating
iron oxidation, iron reduction, iron phase inventories, Butler-Volmer kinetics,
Nernst potential, ORR kinetics, OER kinetics, hydrogen evolution, oxygen limitation,
KOH conductivity, electrolyte concentration, reaction heat, and mass and charge conservation.

Each notebook SHALL call the actual associated Python component.
<<<
COMMENT: >>>
Changed because notebooks/chemistry does not exist. Faraday chemistry is exercised
inside plant_sim component notebooks (01_IronAnode through 04_OER) that import
ironair.chemistry. Dedicated chemistry-only notebooks remain an open allocation
under notebooks/chemistry if created later. Plots are software verification, not
hardware validation of US12308414B2 or EP4602674A1.
<<<

[REQUIREMENT]
UID: IA-NBK-005
STATUS: Active
TITLE: Component demonstrations
STATEMENT: >>>
Every component SHALL have a notebook or explicitly designated notebook section containing
component configuration, initial conditions, input stimulus, simulation execution,
time-domain plots, parameter sensitivity, conservation or physical validation results,
and discussion of observed behavior.
<<<
COMMENT: >>>
Changed because tests/test_notebook_inventory.py does not exist.
plant_sim/01_IronAnode.ipynb through plant_sim/09_Thermal.ipynb plus 10-40
substructure notebooks are the component demonstration inventory.
<<<

[REQUIREMENT]
UID: IA-NBK-006
STATUS: Active
TITLE: Full-system scenario demonstrations
STATEMENT: >>>
The notebook suite SHALL cover the implemented plant_sim scenario notebooks
90_Commissioning through 99_FullPlantMission, driven by plant_sim.scenarios.mission.

Remaining IA-SCN-* identifiers in DOC-SSS003 SHALL stay design allocations until a
dedicated notebook or mission input function exists. The suite SHALL NOT claim that
every SSS003 UID already has an ironair.scenarios function.
<<<
COMMENT: >>>
Changed because ironair.scenarios is empty and Section 9 is not a StrictDoc section.
plant_sim/90-99 notebooks plus plant_sim.scenarios.mission are the executable
coverage; SSS003 still specifies additional design-level cases.
<<<

[REQUIREMENT]
UID: IA-PLT-001
STATUS: Active
TITLE: Notebook seaborn figures
STATEMENT: >>>
A notebook plot SHALL call seaborn in that notebook cell and SHALL display the
figure in the cell output.

Axis labels SHALL include physical units.

A notebook SHALL NOT use a saved image file as the way to show a plot.
File export of figures MAY exist only for a non-notebook script, and that export
SHALL NOT live in ironair and SHALL NOT be the notebook display path.
<<<
COMMENT: >>>
Changed because the shared ironair plotting helper was removed. Notebooks use
sns.set_theme and sns.lineplot. plant_sim/verify_components.py may still write
PNGs through plant_sim/plotting.py, which notebooks do not import.
<<<
RELATIONS:
- TYPE: Parent
  VALUE: IA-NBK-002

[[/SECTION]]

[[SECTION]]
UID: SEC-SSS1-TST
TITLE: Verification, conservation, and reproducibility

[REQUIREMENT]
UID: IA-TST-001
STATUS: Active
TITLE: Elemental conservation
STATEMENT: >>>
The stoichiometric network SHALL conserve chemical elements for every reaction.
<<<
COMMENT: >>>
max(abs(element_matrix @ S)) < 1e-12.
<<<
RELATIONS:
- TYPE: Parent
  VALUE: IA-CHM-010

[REQUIREMENT]
UID: IA-TST-002
STATUS: Active
TITLE: Charge conservation
STATEMENT: >>>
Electrode currents, capacitive currents, and reaction rates SHALL obey conservation of charge.
<<<
COMMENT: >>>
Sum of Faradaic, capacitive, and terminal currents is below 1e-9 A relative residual.
<<<

[REQUIREMENT]
UID: IA-TST-003
STATUS: Active
TITLE: Energy conservation
STATEMENT: >>>
The coupled system SHALL account for electrical, chemical, thermal, and material-flow energy.
<<<
COMMENT: >>>
Closed-system energy residual is reported and below documented tolerance for the adiabatic cell test.
<<<

[REQUIREMENT]
UID: IA-TST-004
STATUS: Active
TITLE: Physical state validity
STATEMENT: >>>
The simulation SHALL reject or explicitly report invalid physical states including negative
species inventory, nonphysical porosity, invalid electrolyte volume, nonphysical absolute
temperature, invalid pressure, impossible oxygen consumption, and nonphysical cell voltage
or current conditions.
<<<
COMMENT: >>>
ironair.exceptions.InvalidPhysicalState is raised or recorded on invalid states.
<<<

[REQUIREMENT]
UID: IA-TST-005
STATUS: Active
TITLE: Numerical convergence
STATEMENT: >>>
The system SHALL include solver tolerance refinement tests and, for spatial models,
mesh refinement tests.
<<<
COMMENT: >>>
Halving rtol reduces trajectory error against a tight-tolerance reference.
<<<

[REQUIREMENT]
UID: IA-TST-006
STATUS: Active
TITLE: Model validation tracking
STATEMENT: >>>
Software verification SHALL be distinguished from model validation.

Experimental calibration and independent physical validation SHALL be separately tracked.
<<<
COMMENT: >>>
Parameter source_class and validation.ValidationRecord never treat unit-test pass as
hardware validation.
<<<

[REQUIREMENT]
UID: IA-TST-007
STATUS: Active
TITLE: Automated unit tests
STATEMENT: >>>
Every exported physical calculation and dynamic component SHALL have automated pytest coverage.
<<<
COMMENT: >>>
pytest coverage for src/ironair is at least 80 percent.
<<<

[REQUIREMENT]
UID: IA-TST-008
STATUS: Active
TITLE: Component integration tests
STATEMENT: >>>
Every coupled component interface SHALL have integration tests verifying dimensions,
units, and conservation.
<<<
COMMENT: >>>
CoupledSystem with a cell plus thermal node conserves charge and reports unit-consistent outputs.
<<<

[REQUIREMENT]
UID: IA-TST-009
STATUS: Active
TITLE: Notebook execution tests
STATEMENT: >>>
Every mandatory notebook SHALL execute from a clean kernel without manual intervention.
<<<
COMMENT: >>>
pytest marker notebook executes required notebooks via nbclient.
<<<

[REQUIREMENT]
UID: IA-TST-010
STATUS: Active
TITLE: Requirements coverage gate
STATEMENT: >>>
CI SHALL fail when a required UID is missing, a requirement has no implementation function,
a required function is missing, a required equation is not tested, a notebook references
an unavailable API, a mandatory notebook fails execution, or conservation acceptance
criteria fail.
<<<
COMMENT: >>>
The traceability test enumerates these failure modes.
<<<

[REQUIREMENT]
UID: IA-TST-011
STATUS: Active
TITLE: Reproducibility
STATEMENT: >>>
The simulation SHALL support deterministic parameter sets, recorded software versions,
and fixed random seeds.
<<<
COMMENT: >>>
SimulationResult.metadata includes ironair version and numpy seed. Sensor noise is
seed-controlled.
<<<

[REQUIREMENT]
UID: IA-DOC-001
STATUS: Active
TITLE: Package documentation
STATEMENT: >>>
The project SHALL publish architecture, API documentation, model limitations,
requirements coverage, and executable notebook demonstrations.
<<<
COMMENT: >>>
README documents install, architecture, limitations, and that passing tests are not
hardware validation of US12308414B2 or EP4602674A1.
<<<

[[/SECTION]]
