[DOCUMENT]
TITLE: Software Requirements Specification - Component ODE Models
UID: DOC-SSS002
VERSION: 1.1.0
OPTIONS:
  MARKUP: Text

[[SECTION]]
UID: SEC-SSS2-ELECTRODES
TITLE: Iron electrode, hydrogen evolution, and dual air electrodes

[TEXT]
STATEMENT: >>>
Each DynamicComponent in this document is the software image of a patented plant
part. Iron, ORR, OER, electrolyte, separator, collector, cell, stack, module,
and enclosure geometries are taken from US12308414B2 (Claims 1-18 and FIGS. 1-93)
and EP4602674A1 (Claims 1-89 and FIGS. 1-27). Balance-of-plant electrical and
thermal components remain required to close the LODES plant of US12308414B2
FIGS. 94-102.
<<<

[REQUIREMENT]
UID: IA-FE-001
STATUS: Active
TITLE: Iron electrode ODE
STATEMENT: >>>
Module plant_sim.components.iron_anode SHALL provide class IronAnode
(notebook plant_sim/01_IronAnode.ipynb).

The component SHALL dynamically model metallic iron, Fe(OH)2, Fe3O4, active surface
area, passivation thickness, porosity, electrode temperature, and irreversible
active-material loss.

The RHS SHALL calculate iron phase derivatives from the shared reaction network.

The iron electrode SHALL support DRI pellet beds (US12308414B2 Claim 18), porous
particle assemblies, and channeled rib-and-spine electrodes (EP4602674A1 Claim 1)
with areal loading 1-7 g Fe/cm2 and electrolyte volume fraction 0.5-0.9 when
fully charged (EP4602674A1 Claim 16-17).

Channel length, width, spacing, shape, slope, channel fraction, and spine/rib
porosity SHALL match IA-SYS-016 and IA-SYS-018. Position relative to ORR and OER
SHALL be changeable (US12308414B2 Claim 13).
<<<
RATIONALE: >>>
US12308414B2 Claim 18 and FIG. 3 packed DRI bed; EP4602674A1 Claims 1, 16-17 and
[0051]-[0061]. Thick electrodes need channels to keep HER from dominating charge.
<<<
COMMENT: >>>
Discharge of Fe increases Fe(OH)2 using IA-CHM-002 stoichiometry. Temperature is a
dynamic state. Passivation thickness is nonnegative.

Changed because ironair.components.iron_electrode / IronElectrode does not exist
(src/ironair/components is an empty package). plant_sim.components.iron_anode.IronAnode
implements the Fe/Fe(OH)2/Fe3O4 Faraday ODE used by the plant stack.
<<<
RELATIONS:
- TYPE: Parent
  VALUE: IA-SYS-003

[REQUIREMENT]
UID: IA-HER-001
STATUS: Active
TITLE: Hydrogen evolution ODE
STATEMENT: >>>
Module plant_sim.components.her SHALL provide class HydrogenEvolution
(notebook plant_sim/02_HER.ipynb).

States SHALL include hydrogen inventory and applicable interfacial or gas-transfer dynamics.

The component SHALL couple hydrogen generation to charging current and electrode potential.

Vertical channels SHALL provide a bubble-egress path for HER (EP4602674A1 [0056]).
Coulombic efficiency SHALL decrease when ionic path length to the back of a thick
iron electrode exceeds the resistance of front-surface HER (EP4602674A1 [0047]).
<<<
RATIONALE: >>>
EP4602674A1 [0044]-[0047], [0056]. Enclosure ventilation and lid venting in
US12308414B2 remove evolved hydrogen from the vessel headspace.
<<<
COMMENT: >>>
H2 inventory increases under negative iron overpotential. Open-circuit HER is smaller
than strong cathodic charging HER.

Changed because ironair.components.hydrogen does not exist. plant_sim.components.her
implements HydrogenEvolution with channel bubble-egress and thick-electrode HER
competition used by the plant stack.
<<<
RELATIONS:
- TYPE: Parent
  VALUE: IA-SYS-020

[REQUIREMENT]
UID: IA-ORR-001
STATUS: Active
TITLE: Oxygen reduction ODE
STATEMENT: >>>
Module plant_sim.components.orr SHALL provide class OxygenReduction
(notebook plant_sim/03_ORR.ipynb).

States SHALL include interfacial charge storage and oxygen availability where applicable.

The component SHALL calculate nonlinear ORR kinetics and oxygen consumption.

ORR SHALL be configurable as floating, vertical natural-air-breathing, inverse
air-breathing, tubular, stacked submerged sections with depth-equalized pressure
drop, wavy/rippled, or bifunctional, per IA-SYS-009 and IA-SYS-012
(US12308414B2 Claims 1, 4, 7-12).

One ORR face SHALL face electrolyte or channels and the opposing face SHALL
contact air (EP4602674A1 Claim 1). Hydrophobic GDE layers with PTFE/carbon MPL
examples from US12308414B2 SHALL be parameterizable.
<<<
RATIONALE: >>>
US12308414B2 Claims 1, 4, 7-12 and cathode construction; EP4602674A1 Claim 1
air-facing second surface.
<<<
COMMENT: >>>
ORR current is negative (cathodic) for eta < 0 versus the ORR Nernst potential.
Oxygen consumption matches Faraday's law for four-electron ORR.

Changed because ironair.components.oxygen_reduction does not exist.
plant_sim.components.orr.OxygenReduction implements stacked/floating/vertical ORR
modes and US Claim 1 equal-dP geometry used by the plant stack.
<<<
RELATIONS:
- TYPE: Parent
  VALUE: IA-SYS-012

[REQUIREMENT]
UID: IA-OER-001
STATUS: Active
TITLE: Oxygen evolution ODE
STATEMENT: >>>
Module plant_sim.components.oer SHALL provide class OxygenEvolution
(notebook plant_sim/04_OER.ipynb).

The component SHALL calculate oxygen evolution, catalyst activity, and applicable
dynamic electrode states.

OER SHALL support planar, submerged, interdigitated trunk-and-projection,
corrugated, serpentine, discrete cathode arrays, spiral bifilar, and pleated
layouts (EP4602674A1 Claims 1, 3, 12, 32, 38, 70, 77).

Default OER construction SHALL be porous metal mesh plus oxygen-evolution
catalyst (Claim 11). OER SHALL sit closer to the iron electrode than ORR during
charge and SHALL be electrically isolatable from ORR (US12308414B2 FIGS. 5A-5B).
<<<
RATIONALE: >>>
EP4602674A1 Claims 1, 3, 11-12, 38, 70, 77; US12308414B2 dual-cathode toggle.
<<<
COMMENT: >>>
OER current is positive (anodic) for eta > 0 versus the OER Nernst potential.

Changed because ironair.components.oxygen_evolution does not exist.
plant_sim.components.oer.OxygenEvolution implements interdigitated/planar OER
layouts and charge-path isolation used by DualElectrodeCell.
<<<
RELATIONS:
- TYPE: Parent
  VALUE: IA-SYS-015

[REQUIREMENT]
UID: IA-GDL-001
STATUS: Active
TITLE: Gas diffusion ODE
STATEMENT: >>>
Module plant_sim.components.gdl SHALL provide class GasDiffusionLayer
(notebook plant_sim/05_GDL.ipynb).

The component SHALL calculate transient oxygen concentration profiles, effective
diffusion, pore saturation, flooding, and gas/liquid transport.

Hydraulic head on vertical ORR SHALL be able to drive liquid migration and
flooding; OER bubbles trapped at a horizontal air electrode SHALL be able to
dry the triple-phase boundary (US12308414B2 vertical versus horizontal
architecture discussion, FIGS. 8-9B). Stacked submerged ORR SHALL capture
cascading bubbles with baffles, lips, or increasing pocket thickness
(FIGS. 25A-36B, Claims 1 and 14-15).
<<<
RATIONALE: >>>
US12308414B2 flooding, dry-out, bubble-trap, and stacked-core air utilization.
pO2 window 0.01-100 atm discharge and 0.001-100 atm charge.
<<<
COMMENT: >>>
A step decrease in boundary O2 mole fraction produces a delayed interior O2 decline.
Flooding (saturation -> 1) reduces effective O2 diffusivity.

Changed because ironair.components.gas_diffusion does not exist.
plant_sim.components.gdl.GasDiffusionLayer implements method-of-lines O2 diffusion,
flooding, and dry-out used by DualElectrodeCell.
<<<
RELATIONS:
- TYPE: Parent
  VALUE: IA-SYS-014

[REQUIREMENT]
UID: IA-ELY-001
STATUS: Active
TITLE: Electrolyte ODE
STATEMENT: >>>
Module plant_sim.components.electrolyte SHALL provide class Electrolyte
(notebook plant_sim/06_Electrolyte.ipynb).

States SHALL include water inventory, dissolved species, electrolyte temperature,
carbonation, and spatial concentration distributions where enabled.

The model SHALL include concentration-dependent KOH physical properties.

Default composition SHALL be 6 M aqueous KOH. Alternate patented mixtures from
IA-SYS-021 SHALL be selectable. Carbonation from CO2-bearing air SHALL consume
OH- and MAY precipitate solids that clog pores (US12308414B2). High hydroxide
(7 M or greater) SHALL be allowed as a capacity and coulombic-efficiency lever
(EP4602674A1).
<<<
RATIONALE: >>>
US12308414B2 electrolyte examples and CO2 discussion; EP4602674A1 Claims 14-15
and high-hydroxide paragraph.
<<<
COMMENT: >>>
Conductivity is computed from instantaneous KOH concentration and temperature via
ironair.properties. Carbonate accumulation consumes OH-.

Changed because ironair.components.electrolyte does not exist.
plant_sim.components.electrolyte.Electrolyte implements 6 M KOH inventory,
carbonation, and fill dynamics used by the plant stack.
<<<
RELATIONS:
- TYPE: Parent
  VALUE: IA-SYS-021

[REQUIREMENT]
UID: IA-SEP-001
STATUS: Active
TITLE: Separator ODE
STATEMENT: >>>
Module plant_sim.components.separator SHALL provide class Separator
(notebook plant_sim/07_Separator.ipynb).

The model SHALL represent transient species transport, electrolyte saturation where
applicable, degradation, and separator temperature.

Ionic resistance SHALL be calculated from the instantaneous physical state.

The separator SHALL be able to block dissolved oxygen and oxygen bubbles from
reaching the iron electrode without a substantial ionic-resistance penalty, while
remaining hydrophilic and macroporous (US12308414B2 FIG. 4A). It MAY be a
compression frame, porous insulator, ribbed bubble-egress structure, or porous
dielectric coating on iron and/or OER (EP4602674A1 [0048], Claim 2). Wrapped
stacked-core separators MAY use 1 micrometer to 1 centimeter pores
(US12308414B2 FIG. 36A).
<<<
RATIONALE: >>>
US12308414B2 oxygen-blocking separator; EP4602674A1 Claim 2 and [0048].
<<<
COMMENT: >>>
R_ionic is algebraic in conductivity, thickness, area, and saturation. Temperature
is dynamic.

Changed because ironair.components.separator does not exist.
plant_sim.components.separator.Separator implements hydrophilic O2-blocking
separator resistance and saturation used by DualElectrodeCell.
<<<
RELATIONS:
- TYPE: Parent
  VALUE: IA-SYS-025

[REQUIREMENT]
UID: IA-COL-001
STATUS: Active
TITLE: Current collector ODE
STATEMENT: >>>
Module plant_sim.components.current_collector SHALL provide class CurrentCollector
(notebook plant_sim/08_CurrentCollector.ipynb).

The model SHALL include thermal dynamics and configurable long-term contact or
resistance degradation.

Ohmic voltage loss SHALL be calculated algebraically.

Collectors SHALL include anode branch-plus-primary layouts, ORR dual-face tabs,
Ni-coated-steel ORR collectors with EPDM gasket compression
(US12308414B2 FIGS. 4B-4C), stainless-steel wires/sheets or mesh cages in iron
ribs (EP4602674A1), and can-negative housings (US12308414B2 Claim 5).
<<<
RATIONALE: >>>
US12308414B2 Claims 5 and 17 and FIGS. 4B-4C; EP4602674A1 Claims 13, 30-31.
<<<
COMMENT: >>>
No fake lag state for resistance. V_ohm = I * R(T, degradation_state).

Changed because ironair.components.current_collector does not exist.
plant_sim.components.current_collector.CurrentCollector implements algebraic Ohmic
drop with thermal and degradation states used by the plant stack.
<<<
RELATIONS:
- TYPE: Parent
  VALUE: IA-SYS-025

[REQUIREMENT]
UID: IA-CEL-001
STATUS: Active
TITLE: Complete cell ODE
STATEMENT: >>>
Module plant_sim.substructures.dual_electrode_cell SHALL provide class DualElectrodeCell
(notebook plant_sim/12_DualElectrodeCell.ipynb).

The cell SHALL couple iron electrode, air electrode, hydrogen evolution, electrolyte,
separator, gas diffusion, current collectors, and thermal dynamics.

The cell SHALL calculate instantaneous terminal voltage, current, power, SOC, and
available capacity.

The component SHALL solve coupled nonlinear electrochemical and electrical constraints.

Charge SHALL close iron to OER to power source; discharge SHALL close iron to ORR
to load (EP4602674A1 [0049]). Independent charge and discharge length scales
SHALL be parameterizable (US12308414B2 Lc versus Ld, including 100 h / 300 h
asymmetric example). Shared-electrolyte baths of multiple cells SHALL be allowed
(US12308414B2 FIG. 9A vessel 970).
<<<
RATIONALE: >>>
EP4602674A1 dual-electrode switch; US12308414B2 dual-cathode and duration scaling.
<<<
COMMENT: >>>
Cell rhs solves algebraic current/voltage consistency. Outputs include V, I, P, SOC.

Changed because ironair.components.cell.IronAirCell does not exist.
plant_sim.substructures.dual_electrode_cell.DualElectrodeCell couples Fe/HER/ORR/OER/GDL/electrolyte/separator
and switches charge (iron-OER) versus discharge (iron-ORR) per EP [0049].
<<<
RELATIONS:
- TYPE: Parent
  VALUE: IA-SYS-008

[[/SECTION]]

[[SECTION]]
UID: SEC-SSS2-BOP
TITLE: Thermal, air, and electrolyte hydraulic plant

[REQUIREMENT]
UID: IA-THM-001
STATUS: Active
TITLE: Thermal ODE
STATEMENT: >>>
Module plant_sim.components.thermal SHALL provide class ThermalNetwork
(notebook plant_sim/09_Thermal.ipynb).

States SHALL include thermal energy or temperature at relevant physical nodes.

The model SHALL calculate conduction, convection, radiation, reaction heat, and cooling.

Vessel cavity flow (air or liquid), thermal-mass water fill, and lid-level thermal
management from US12308414B2 FIGS. 1E-1F and 9A SHALL map onto ThermalNetwork
nodes. Wide/low vessels SHALL be usable to increase surface area for heat
rejection.
<<<
RATIONALE: >>>
US12308414B2 double-wall cavity 161 and multi-function lid thermal management.
<<<
COMMENT: >>>
Adiabatic isolated node with positive heat source increases temperature.

Changed because ironair.components.thermal does not exist.
plant_sim.components.thermal.ThermalNetwork implements electrode/electrolyte/vessel/lid/cavity
nodes from US FIGS. 1E-1F and 9A.
<<<
RELATIONS:
- TYPE: Parent
  VALUE: IA-SYS-011

[REQUIREMENT]
UID: IA-AIR-001
STATUS: Active
TITLE: Air handling ODE
STATEMENT: >>>
Module plant_sim.components.air_system SHALL provide class AirSystem
(notebooks plant_sim/22_VesselLidAir.ipynb and plant_sim/32_AirHandling.ipynb).

The component SHALL include gas inventories, manifold pressure dynamics, oxygen
concentration, humidity, and airflow coupling.

Air delivery SHALL include natural air-breathing, forced supply, sparging/bubbling
into submerged ORR, cascading stacked-core flow, snorkel/test-tube mixed-phase
channels, and ramp arrays with holes (US12308414B2 Claims 9, 14-15; FIGS. 37-51,
71A-71B). Outlet pressure regulation SHALL be able to hold unsealed air-chamber
pressure.
<<<
RATIONALE: >>>
US12308414B2 air-supply and stacked-core architectures. Equal pressure drop across
depth-stacked ORR sections is Claim 1.
<<<
COMMENT: >>>
Manifold pressure rises when inlet mass flow exceeds outlet plus consumption.

Changed because ironair.components.air_system does not exist.
plant_sim.components.air_system.AirSystem implements manifold pressure, O2/N2/H2O/CO2
inventories used by VesselLidAir and the full plant.
<<<
RELATIONS:
- TYPE: Parent
  VALUE: IA-SYS-014

[REQUIREMENT]
UID: IA-AIR-002
STATUS: Active
TITLE: Fan ODE
STATEMENT: >>>
Module plant_sim.components.air_system SHALL provide class Fan
(same module as AirSystem; notebooks plant_sim/22_VesselLidAir.ipynb and plant_sim/32_AirHandling.ipynb).

The model SHALL include rotor speed dynamics and fan power consumption.

Fan/blower air SHALL be able to feed submerged ORR stacks and lid air-distribution
plenums of US12308414B2 FIG. 9A.
<<<
COMMENT: >>>
Rotor speed is a dynamic state. Electrical power is an algebraic output from speed and torque.

Changed because ironair.components.fan does not exist. Fan lives in
plant_sim.components.air_system beside AirSystem, matching the coupled lid-air plant.
<<<
RELATIONS:
- TYPE: Parent
  VALUE: IA-AIR-001

[REQUIREMENT]
UID: IA-FLD-001
STATUS: Active
TITLE: Electrolyte circulation ODE
STATEMENT: >>>
Module plant_sim.components.hydraulics SHALL provide class ElectrolyteFlow
(notebook plant_sim/31_Hydraulics.ipynb).

The component SHALL dynamically track flow, species transfer, pressure or hydraulic
storage where physically justified, and temperature.
<<<
COMMENT: >>>
Species transport delay appears when using the detailed hydraulic mode.

Changed because ironair.components.electrolyte_flow does not exist.
plant_sim.components.hydraulics.ElectrolyteFlow implements circulation mass-flow,
header pressure, and loop temperature used by HydraulicsBOP.
<<<
RELATIONS:
- TYPE: Parent
  VALUE: IA-SYS-021

[REQUIREMENT]
UID: IA-FLD-002
STATUS: Active
TITLE: Pump ODE
STATEMENT: >>>
Module plant_sim.components.hydraulics SHALL provide class Pump
(notebook plant_sim/31_Hydraulics.ipynb).

The component SHALL model motor and hydraulic response, electrical input, and mechanical losses.
<<<
COMMENT: >>>
Shaft speed is dynamic. Hydraulic power is less than electrical input by documented efficiency.

Changed because ironair.components.pump does not exist.
plant_sim.components.hydraulics.Pump implements shaft-speed dynamics with documented
electrical-to-hydraulic efficiency.
<<<
RELATIONS:
- TYPE: Parent
  VALUE: IA-SYS-021

[REQUIREMENT]
UID: IA-FLD-003
STATUS: Active
TITLE: Reservoir ODE
STATEMENT: >>>
Module plant_sim.components.hydraulics SHALL provide class Reservoir
(notebook plant_sim/31_Hydraulics.ipynb).

The component SHALL model liquid inventory, chemical species inventories, temperature,
and boundary flows.
<<<
COMMENT: >>>
Mass balance: dM/dt equals inlet minus outlet minus leak.
The vessel cavity MAY hold drained electrolyte during maintenance
(US12308414B2 FIGS. 1E-1F) without requiring off-site storage volume.

Changed because ironair.components.reservoir does not exist.
plant_sim.components.hydraulics.Reservoir implements mass, OH inventory, leak path,
and fill used by commissioning and hydraulics BOP.
<<<
RELATIONS:
- TYPE: Parent
  VALUE: IA-SYS-021

[REQUIREMENT]
UID: IA-FLD-004
STATUS: Active
TITLE: Valve ODE
STATEMENT: >>>
Module plant_sim.components.hydraulics SHALL provide class Valve
(notebook plant_sim/31_Hydraulics.ipynb).

The component SHALL model actuator response, valve position, and flow-dependent
hydraulic characteristics.
<<<
COMMENT: >>>
Position is a dynamic actuator state. Flow is algebraic in position and pressure drop.

Changed because ironair.components.valve does not exist.
plant_sim.components.hydraulics.Valve implements first-order actuator position with
algebraic orifice flow.
<<<
RELATIONS:
- TYPE: Parent
  VALUE: IA-SYS-021

[REQUIREMENT]
UID: IA-FLD-005
STATUS: Active
TITLE: Piping ODE
STATEMENT: >>>
Module plant_sim.components.hydraulics SHALL provide class Pipe
(notebook plant_sim/31_Hydraulics.ipynb).

The component SHALL model transient fluid transport and temperature or species
residence-time dynamics when using the detailed hydraulic mode.
<<<
COMMENT: >>>
Detailed mode has at least one transport delay state. Lumped mode is flagged reduced_order.

Changed because ironair.components.piping does not exist.
plant_sim.components.hydraulics.Pipe implements a transport-delay concentration/temperature
state used by HydraulicsBOP.
<<<
RELATIONS:
- TYPE: Parent
  VALUE: IA-SYS-021

[REQUIREMENT]
UID: IA-HEX-001
STATUS: Active
TITLE: Heat exchanger ODE
STATEMENT: >>>
Module plant_sim.components.thermal SHALL provide class HeatExchanger
(notebook plant_sim/09_Thermal.ipynb).

The component SHALL represent thermal storage and dynamic heat transfer between fluid circuits.
<<<
COMMENT: >>>
Two fluid temperatures approach each other under heat transfer with no external loss.
Cavity coolant and lid thermal loops of US12308414B2 SHALL be representable as
HeatExchanger circuits.

Changed because ironair.components.heat_exchanger does not exist.
plant_sim.components.thermal.HeatExchanger implements two-stream thermal storage
used by the plant cavity/lid cooling loops.
<<<
RELATIONS:
- TYPE: Parent
  VALUE: IA-THM-001

[[/SECTION]]

[[SECTION]]
UID: SEC-SSS2-PLANT
TITLE: Stack, module, enclosure, and electrical conversion

[REQUIREMENT]
UID: IA-STK-001
STATUS: Active
TITLE: Stack ODE
STATEMENT: >>>
Module plant_sim.substructures.cell_stack SHALL provide class CellStack
(notebooks plant_sim/20_CellStack.ipynb and plant_sim/96_EqualPressureDropORR.ipynb).

The component SHALL aggregate cell states while preserving cell-level variations and
electrical current conservation.

Stacked vessels with conductive contact points SHALL be able to place cells in
series (US12308414B2 Claim 3). Arrays of coaxial ORR-core / hexagonal-anode cells
in a shared electrolyte pool (FIGS. 27-34) and multi-cell housings with dividing
walls (FIG. 13) SHALL be supported. Double-sided and air-channel-paired cells
from EP4602674A1 Claims 18-19 SHALL be stackable.
<<<
RATIONALE: >>>
US12308414B2 Claims 3 and 5, FIGS. 13 and 27-34; EP4602674A1 Claims 18-19.
<<<
COMMENT: >>>
Series stack current is identical through cells. Terminal voltage is the sum of cell voltages.

Changed because ironair.components.stack.BatteryStack does not exist.
plant_sim.substructures.cell_stack.CellStack series-aggregates DualElectrodeCell and
exposes US Claim 1 equal-dP stacked ORR geometry.
<<<
RELATIONS:
- TYPE: Parent
  VALUE: IA-SYS-011

[REQUIREMENT]
UID: IA-MOD-001
STATUS: Active
TITLE: Module ODE
STATEMENT: >>>
Module plant_sim.substructures.module SHALL provide class BatteryModule
(notebook plant_sim/30_Module.ipynb).

The model SHALL include coupled stacks, shared fluid equipment, air equipment, and thermal states.

A module MAY be a stack of 40 housings as illustrated in US12308414B2 FIG. 13,
sharing lid air distribution, venting, and DC connections (FIG. 9A).
<<<
COMMENT: >>>
Module assembles at least one stack plus shared thermal or fluid nodes.

Changed because ironair.components.module does not exist.
plant_sim.substructures.module.BatteryModule wraps PlantModel with documented
series/parallel housing counts from US FIG. 13.
<<<
RELATIONS:
- TYPE: Parent
  VALUE: IA-SYS-011

[REQUIREMENT]
UID: IA-ENC-001
STATUS: Active
TITLE: Enclosure ODE
STATEMENT: >>>
Module plant_sim.substructures.vessel_lid_air SHALL provide class VesselLidAir
(notebook plant_sim/22_VesselLidAir.ipynb).

The model SHALL include enclosure temperature, ventilation, auxiliary electrical loads,
and enclosure-level gas inventories.

The enclosure SHALL implement stackable-vessel, double-wall secondary containment,
optional bag-in-box, trough/dished mechanical shapes, and multi-function lid
(air distribution, process-gas vent, thermal management, current collection,
controls/sensing, DC connections) from US12308414B2 Claims 3 and 5 and
FIGS. 1E-1F, 9A, 12A-12F. Alkaline electrolyte SHALL have primary plus secondary
containment.
<<<
RATIONALE: >>>
US12308414B2 Claim 3 vessel, Claim 5 can-negative housing, hazardous-electrolyte
containment, and lid 902 functions.
<<<
COMMENT: >>>
Ventilation flow reduces enclosure H2 inventory. Auxiliary load is an algebraic electrical output.

Changed because ironair.components.enclosure.BatteryEnclosure does not exist.
plant_sim.substructures.vessel_lid_air.VesselLidAir implements stackable vessel, DRI bed,
lid air delivery, and thermal cavity used as the enclosure image.
<<<
RELATIONS:
- TYPE: Parent
  VALUE: IA-SYS-026

[REQUIREMENT]
UID: IA-DC-001
STATUS: Active
TITLE: DC bus ODE
STATEMENT: >>>
Module plant_sim.components.electrical SHALL provide class DCBus
(notebook plant_sim/33_ElectricalBalance.ipynb).

The component SHALL model DC link capacitor voltage and stored energy.
<<<
COMMENT: >>>
C * V * dV/dt equals net electrical power into the capacitor.

Changed because ironair.components.dc_bus does not exist.
plant_sim.components.electrical.DCBus implements capacitor voltage dynamics used by
ElectricalBalance and PlantModel.
<<<
RELATIONS:
- TYPE: Parent
  VALUE: IA-SYS-007

[REQUIREMENT]
UID: IA-CNV-001
STATUS: Active
TITLE: DC/DC converter ODE
STATEMENT: >>>
Module plant_sim.components.electrical SHALL provide class DCDCConverter
(notebook plant_sim/33_ElectricalBalance.ipynb).

The model SHALL include averaged inductor current, capacitor voltage, and converter losses.
<<<
COMMENT: >>>
Averaged inductor current is a dynamic state. Losses increase output current demand.

Changed because ironair.components.dc_converter does not exist.
plant_sim.components.electrical.DCDCConverter implements averaged inductor/capacitor
states used by ElectricalBalance.
<<<
RELATIONS:
- TYPE: Parent
  VALUE: IA-DC-001

[REQUIREMENT]
UID: IA-INV-001
STATUS: Active
TITLE: Inverter ODE
STATEMENT: >>>
Module plant_sim.components.electrical SHALL provide class GridInverter
(notebook plant_sim/33_ElectricalBalance.ipynb).

The model SHALL include averaged electrical control dynamics, DC link interaction,
and active/reactive power response.
<<<
COMMENT: >>>
P and Q track references through explicit controller states, not prescribed algebraic jumps only.

Changed because ironair.components.inverter does not exist.
plant_sim.components.electrical.GridInverter implements P/Q tracker states used by
PlantModel grid exchange.
<<<
RELATIONS:
- TYPE: Parent
  VALUE: IA-DC-001

[REQUIREMENT]
UID: IA-TRF-001
STATUS: Active
TITLE: Transformer ODE
STATEMENT: >>>
Module plant_sim.components.electrical SHALL provide class Transformer
(notebook plant_sim/33_ElectricalBalance.ipynb).

The component SHALL include electromagnetic dynamic states where detailed transient
modeling is enabled, along with winding and core thermal dynamics.
<<<
COMMENT: >>>
Detailed mode includes flux or current states. Thermal states exist in both modes.
Prescribed grid voltage is an input, not a transformer state.

Changed because ironair.components.transformer does not exist.
plant_sim.components.electrical.Transformer implements flux and winding-temperature
states with grid voltage as an input.
<<<
RELATIONS:
- TYPE: Parent
  VALUE: IA-GRD-001

[REQUIREMENT]
UID: IA-GRD-001
STATUS: Active
TITLE: Grid interface ODE
STATEMENT: >>>
Module plant_sim.components.electrical SHALL provide class GridInterface
(notebooks plant_sim/33_ElectricalBalance.ipynb and plant_sim/92_GridServices.ipynb).

The grid SHALL support dynamic voltage and frequency disturbances, network interface
equations, and configurable external-grid dynamic models.

A prescribed grid voltage or frequency SHALL be treated as an external input, not an
invented dynamic state.

Grid-connected LODES dispatch of surplus solar over seasonal windows
(US12308414B2 Definitions; FIGS. 94-102 bulk energy storage systems) SHALL be
representable as GridInterface scenarios.
<<<
COMMENT: >>>
When voltage/frequency are prescribed, they appear in inputs. Optional swing-equation
mode is explicitly identified.

Changed because ironair.components.grid does not exist.
plant_sim.components.electrical.GridInterface treats v/f as inputs and filters
exchange power for LODES dispatch scenarios.
<<<
RELATIONS:
- TYPE: Parent
  VALUE: IA-SYS-007

[REQUIREMENT]
UID: IA-DEG-001
STATUS: Active
TITLE: Degradation ODE
STATEMENT: >>>
Module plant_sim.components.degradation SHALL provide class Degradation
(notebook plant_sim/98_DegradationCE.ipynb).

The model SHALL represent irreversible material changes, catalyst decay, resistance
growth, and active capacity loss.

ORR damage from high OER potential, PTFE hydrophobicity loss, carbonate pore
clogging, salt crusting on air electrodes, and iron passivation SHALL be
representable aging modes (US12308414B2 dual-cathode isolation, CO2, and crusting
discussion; EP4602674A1 passivation via Fe(OH)2 films). Seasonal anode replacement
SHALL be an allowed discrete maintenance event (US12308414B2 replaceable electrodes).
<<<
COMMENT: >>>
Degradation states are nondecreasing under positive aging rates. Capacity loss is irreversible.

Changed because ironair.components.degradation does not exist.
plant_sim.components.degradation.Degradation implements ORR damage, PTFE loss,
carbonate ASR growth, and irreversible capacity loss used by PlantModel.
<<<
RELATIONS:
- TYPE: Parent
  VALUE: IA-SYS-023

[REQUIREMENT]
UID: IA-FLT-001
STATUS: Active
TITLE: Sensor ODE
STATEMENT: >>>
Lid-mounted voltage, current, temperature, electrolyte-level, gas-flow, and
hydrogen sensing from US12308414B2 FIG. 9A SHALL remain a design-only requirement
until a sensor ODE exists. No plant_sim or ironair DynamicSensor class is
implemented.

When implemented, the model SHALL include finite response time, sensor drift,
bias, and noise with a documented random seed. It SHALL NOT claim
ironair.components.sensors until that module exists.
<<<
COMMENT: >>>
Changed because ironair.components.sensors.DynamicSensor does not exist and no
plant_sim sensor ODE was implemented with the plant stack. Leaving a module SHALL
would be a false implementation claim; this UID is now an explicit design allocation.
<<<
RELATIONS:
- TYPE: Parent
  VALUE: IA-SYS-011

[REQUIREMENT]
UID: IA-CTL-001
STATUS: Active
TITLE: Supervisory control dynamics
STATEMENT: >>>
Module plant_sim.plant SHALL provide class PlantModel with discrete operating modes
MODE_CHARGE, MODE_DISCHARGE, MODE_REST, and MODE_COMMISSION
(notebooks plant_sim/12_DualElectrodeCell.ipynb and plant_sim/40_PlantModel.ipynb).

Charge SHALL close iron-OER-source and discharge SHALL close iron-ORR-load with
optional ORR isolation from OER potential (EP4602674A1 switch 116; US12308414B2
switch 550 and Claim 16).

ironair.controls.supervisory.SupervisoryController is not implemented; mode
switching currently lives in PlantModel.algebraic until a dedicated controller
module exists.
<<<
COMMENT: >>>
Changed because ironair.controls.supervisory.SupervisoryController does not exist
(src/ironair/controls is an empty package). PlantModel already implements the
patented dual-electrode mode switch used by the plant stack.
<<<
RELATIONS:
- TYPE: Parent
  VALUE: IA-SYS-008

[REQUIREMENT]
UID: IA-EST-001
STATUS: Active
TITLE: State estimation
STATEMENT: >>>
Battery state estimation (SOC, SOH, active iron inventory, and available
charge/discharge power) SHALL remain a design-only requirement until an observer
module exists. No ironair.controls.estimation.BatteryStateEstimator class is
implemented.

When implemented, the estimator SHALL accept measurements and prior estimates only
and SHALL NOT receive the plant hidden state vector during observer execution.
<<<
COMMENT: >>>
Changed because ironair.controls.estimation.BatteryStateEstimator does not exist
(src/ironair/controls is an empty package) and plant_sim has no observer.
Leaving a module SHALL would be a false implementation claim.
<<<
RELATIONS:
- TYPE: Parent
  VALUE: IA-CTL-001

[[/SECTION]]
